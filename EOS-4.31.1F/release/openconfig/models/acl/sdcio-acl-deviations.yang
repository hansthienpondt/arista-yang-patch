module sdcio-acl-deviations {
  namespace "http://sdcio.dev/yang/openconfig/acl/deviations";
  prefix sdcio-acl-deviations;

  import openconfig-inet-types {
    prefix oc-inet;
  }
  import openconfig-acl {
    prefix oc-acl;
  }
  import openconfig-packet-match-types {
    prefix oc-pkt-match-types;
  }
  import openconfig-extensions {
    prefix oc-ext;
  }

  organization
    "Schema Driven Configuration";
  contact
    "https://github.com/sdcio";
  description
    "This module contains OpenConfig ACL deviations for Arista EOS. in SDCIO";

  oc-ext:openconfig-version "1.0.0";

  revision 2024-11-07 {
    description
      "Initial Release, remove oc-acl:acl-entry/oc-acl:state from ingress-acl-sets and egress-acl-sets";
    reference
      "1.0.0";
  }
}
